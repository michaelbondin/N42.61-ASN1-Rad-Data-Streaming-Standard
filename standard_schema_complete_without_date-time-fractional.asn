-- Edited 07/12/2022 --
-- Complete ASN.1 Schema for ANSI N42.61: Wireless Radiation Data Streaming Standard --
-- BEGIN --
StandardSpecification DEFINITIONS AUTOMATIC TAGS ::= BEGIN
	PacketType ::= CHOICE
		{
		headerpacket Header,
		status InstrumentStatus,
		data RadiationData,
		footerpacket Footer,
		...}

	-- Begin Header --
	Header ::= SEQUENCE {
		timeInformationHeader SEQUENCE
		{
			timeStampZero DATE-TIME,
			radiationDataPacketTransmissionRate REAL OPTIONAL,
			instrumentStatusPacketTransmissionRate REAL OPTIONAL,
			...
		},
		instrumentInformationHeader SEQUENCE
		{
			instrumentName UTF8String,
			instrumentDescription UTF8String OPTIONAL,
			instrumentManufacturer UTF8String,
			instrumentModel UTF8String,
			instrumentSerialNumber UTF8String,
			instrumentFirmware UTF8String OPTIONAL,
			instrumentFirmwareVersion UTF8String OPTIONAL,
			instrumentSoftware UTF8String OPTIONAL,
			instrumentSoftwareVersion UTF8String OPTIONAL,
			numberOfDetectors INTEGER OPTIONAL,
			...
		},
		detectorsListHeader SEQUENCE OF detectorInformationHeader SEQUENCE
		{
			detectorID INTEGER,
			detectorType ENUMERATED
				{
					grossGamma				(0),
					grossNeutron			(1),
					spectroscopic 			(2),
					spectroscopicRIID		(3),
					grossAlpha				(4),
					grossBeta				(5),
					...
				},
			detectorKind ENUMERATED
				{
					hPGe 	(0),
					hPXe	(1),
					naI		(2),
					laBr3	(3),
					laCl3	(4),
					bGO		(5),
					cZT		(6),
					cdT		(7),
					csI		(8),
					gMT		(9),
					gMTW	(10),
					liFiber	(11),
					pVT		(12),
					pS		(13),
					he3		(14),
					he4		(15),
					liGlass	(16),
					liI		(17),
					srI2	(18),
					cLYC	(19),
					cdWO4	(20),
					bF3		(21),
					hgI2	(22),
					ceBr4	(23),
					liCAF	(24), 
					liZnS	(25),
					cLLBC	(26), 
					plastic	(27),
					znSAG	(28),
					other	(29),
					...
				} OPTIONAL,
			detectorDescription UTF8String OPTIONAL,
			detectorManufacturer UTF8String OPTIONAL,
			detectorModel UTF8String OPTIONAL,
			detectorSerialNumber UTF8String OPTIONAL,
			detectorFirmware UTF8String OPTIONAL,
			detectorFirmwareVersion UTF8String OPTIONAL,
			detectorSoftware UTF8String OPTIONAL,
			detectorSoftwareVersion UTF8String OPTIONAL,
			exposureCoeff REAL OPTIONAL,
			doseConversionCoeff REAL OPTIONAL,
			spectrumCompression BOOLEAN OPTIONAL,
			backgroundSubtraction BOOLEAN OPTIONAL,
			numberOfMCAChannels INTEGER OPTIONAL,
			calibration SEQUENCE
			{
				calibrationTemperaturesList SEQUENCE OF INTEGER OPTIONAL,
				calibrationEnergiesList SEQUENCE OF REAL OPTIONAL,
				calibrationChannelsList SEQUENCE OF SEQUENCE OF INTEGER OPTIONAL,
				calibrationTime DATE-TIME OPTIONAL,
				energyBinsStructure CHOICE
					{
					energyBinsCoefficients SEQUENCE OF REAL,
					energyBinsList SEQUENCE OF REAL,
					...
					} OPTIONAL,
				...
			} OPTIONAL,
			...
		},
		endHeaderPacket BIT STRING OPTIONAL,
		...
	}
	-- End Header --

	-- Begin Instrument Status --
	InstrumentStatus ::= SEQUENCE
	{
		instrumentStatusPacketNumber INTEGER,
		timeInformationInstrumentStatus SEQUENCE
		{
			relativeTime INTEGER,
			timeStamp DATE-TIME OPTIONAL,
			...
		},

		instrumentStatusInformation SEQUENCE
		{
			instrumentTemperature INTEGER OPTIONAL,
			instrumentPower CHOICE
			{
				instrumentBatteryRemainingCharge INTEGER,
				instrumentBatteryVoltage REAL,
				instrumentPowerStatus BOOLEAN,
				...
			} OPTIONAL,
			instrumentHealth BOOLEAN OPTIONAL,
			instrumentSelfCalibration BOOLEAN OPTIONAL,
			...
		} OPTIONAL,
		detectorsListInformationStatus SEQUENCE OF detectorStatusInformation SEQUENCE
		{
			detectorID INTEGER,
			detectorManufacturer UTF8String OPTIONAL,
			detectorModel UTF8String OPTIONAL,
			detectorSerialNumber UTF8String OPTIONAL,
			detectorVoltage REAL OPTIONAL,
			detectorGain UTF8String OPTIONAL,
			detectorTemperature INTEGER OPTIONAL,
			detectorHealth BOOLEAN OPTIONAL,
			...
		},
		...
	}
	-- End Instrument Status --


	-- Begin Radiation Data --
	RadiationData ::= SEQUENCE {
		radiationDataPacketNumber INTEGER OPTIONAL,
		timeInformationRadiationData SEQUENCE
		{
			relativeTime INTEGER,
			accumulationTime INTEGER,
			timeStamp DATE-TIME OPTIONAL,
			...
		},
		detectorsListRadiationData SEQUENCE OF detectorRadiationData SEQUENCE
		{
			detectorID INTEGER OPTIONAL,
			counts INTEGER,
			channelSpectrum SEQUENCE OF INTEGER OPTIONAL,
			derivedData SEQUENCE
			{
				countRate REAL OPTIONAL,
				exposure REAL OPTIONAL,
				exposureRate REAL OPTIONAL,
				dose REAL OPTIONAL,
				doseRate REAL OPTIONAL,
				intensity INTEGER OPTIONAL,
				energySpectrum SEQUENCE
					{
					energyBinList SEQUENCE OF REAL OPTIONAL,
					energyBinCountsList SEQUENCE OF INTEGER OPTIONAL,
					...
					} OPTIONAL,
				alarm1 BOOLEAN OPTIONAL,
				alarm2 BOOLEAN OPTIONAL,
				alarm3 BOOLEAN OPTIONAL,
				deadTime REAL OPTIONAL,
				liveTime REAL OPTIONAL,
				identificationResults SEQUENCE OF identifiedMaterial SEQUENCE
				{
					identifiedRadionuclide OCTET STRING OPTIONAL,
					category UTF8String OPTIONAL,
					-- category ENUMERATED OPTIONAL
					-- {
					--	snm 			(0),
					--	norm			(1),
					--	industrial		(2),
					--	medical			(3),
					--	unidentified	(4),
					--	...

					--},
					confidenceLevel INTEGER OPTIONAL,
					...
				} OPTIONAL,
				...
			} OPTIONAL,
			...
		},
		...
	}
	-- End Radiation Data --

	-- Begin Footer --
	Footer ::= SEQUENCE {
		timeInformationFooter SEQUENCE
		{
			relativeTime INTEGER,
			timeStamp DATE-TIME,
			...
		},
		lastInstrumentStatusPacketNumber INTEGER OPTIONAL,
		lastRadiationDataPacketNumber INTEGER OPTIONAL,
		endFooterPacket BIT STRING OPTIONAL,
		...
	}
	-- End Footer --

END
